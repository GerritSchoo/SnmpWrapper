KEYWORD-MIB DEFINITIONS ::= BEGIN

-- Descriptors that are C++ keywords or names the generated code uses itself:
-- the generator must turn them into valid identifiers (trailing '_'), and the code must compile.

IMPORTS
    MODULE-IDENTITY, OBJECT-TYPE, Integer32, enterprises
        FROM SNMPv2-SMI
    DisplayString
        FROM SNMPv2-TC;

keywordMIB MODULE-IDENTITY
    LAST-UPDATED "202610300000Z"
    ORGANIZATION "snmpwrap test"
    CONTACT-INFO "none"
    DESCRIPTION  "C++ keywords as MIB names."
    REVISION     "202610300000Z"
    DESCRIPTION  "Initial version."
    ::= { enterprises 99999 320 }

namespace OBJECT IDENTIFIER ::= { keywordMIB 1 }

default OBJECT-TYPE
    SYNTAX      Integer32 (0..10)
    MAX-ACCESS  read-write
    STATUS      current
    DESCRIPTION "A keyword."
    ::= { namespace 1 }

class OBJECT-TYPE
    SYNTAX      DisplayString (SIZE (0..8))
    MAX-ACCESS  read-write
    STATUS      current
    DESCRIPTION "A keyword."
    ::= { namespace 2 }

register OBJECT-TYPE
    SYNTAX      INTEGER { delete(1), new(2), true(3) }
    MAX-ACCESS  read-write
    STATUS      current
    DESCRIPTION "A keyword with keyword labels."
    ::= { namespace 3 }

validate OBJECT-TYPE
    SYNTAX      Integer32
    MAX-ACCESS  read-only
    STATUS      current
    DESCRIPTION "Clashes with Data::validate()."
    ::= { namespace 4 }

status OBJECT-TYPE
    SYNTAX      Integer32
    MAX-ACCESS  read-only
    STATUS      current
    DESCRIPTION "A name the generated code uses."
    ::= { keywordMIB 2 }

END
